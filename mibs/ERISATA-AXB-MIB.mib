ERISATA-AXB-MIB DEFINITIONS ::= BEGIN

    IMPORTS
        MODULE-IDENTITY     FROM SNMPv2-SMI
        erisata             FROM ERISATA-MIB
        ;

    axb MODULE-IDENTITY
        LAST-UPDATED "201601070000Z"
        ORGANIZATION "UAB Erisata"
        CONTACT-INFO
            "Karolis Petrauskas
             UAB Erisata
             Vivulskio 15-3, Vilnius
             karolis.petrauskas@erisata.lt"
        DESCRIPTION "Root SNMP module for the AxB application (and all its modules)."
        REVISION "201601070000Z"
        DESCRIPTION "Initial revision."
        ::= { erisata 3 }

END
